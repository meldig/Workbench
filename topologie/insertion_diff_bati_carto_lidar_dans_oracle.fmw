FME workspace insertion_diff_bati_carto_lidar_dans_oracle.fmw

Parameters:
- SourceDataset_ESRISHAPE_7 = $(FME_MF_DIR)donnees\v_fin\differences\differences_avec_objectid_plan_gestion\ta_bati_carto_single_uniquement_objectid.shp   # Source Esri Shapefile(s)
- SourceDataset_ESRISHAPE_8 = $(FME_MF_DIR)donnees\v_fin\differences\ta_bati_lidar_uniquement.shp   # Source Esri Shapefile(s)
- DestDataset_ORACLE_SPATIAL_7 = GEO   # Connection
- DestDataset_ORACLE_SPATIAL_8 = GEO   # Connection

Readers:
- ESRISHAPE_3: ESRISHAPE from $(SourceDataset_ESRISHAPE_7) in EPSG:2154
- ESRISHAPE_4: ESRISHAPE from $(SourceDataset_ESRISHAPE_8) in EPSG:2154

Writers:
- ORACLE_SPATIAL_4: ORACLE_SPATIAL to $(DestDataset_ORACLE_SPATIAL_7) in EPSG:2154
- ORACLE_SPATIAL_5: ORACLE_SPATIAL to $(DestDataset_ORACLE_SPATIAL_8) in EPSG:2154

Bookmark: Insertion des différences de bâti du LiDAR par rapport au Plan de Gestion dans TEMP_DIFF_CARTO_LIDAR
ta_bati_lidar_uniquement (reader ESRISHAPE_4)
    -> TEMP_DIFF_CARTO_LIDAR (writer ORACLE_SPATIAL_4)
TEMP_DIFF_CARTO_LIDAR (writer ORACLE_SPATIAL_4)
    attributes: OBJECTID number(38,0), FID_LIBELLE number(38,0), ID_CARTO number(38,0), fme_geomattr{7}.oracle_secondary_radius float, fme_geomattr{7}.oracle_start_angle float, fme_geomattr{7}.oracle_rotation float, fme_geomattr{8}.oracle_primary_radius float, fme_geomattr{8}.oracle_rotation float, fme_geomattr{7}.oracle_sweep_angle float, fme_geomattr{8}.oracle_secondary_radius float, fme_geomattr{7}.oracle_primary_radius float

Bookmark: Insertion des différences de bâti du Plan de Gestion par rapport au LiDAR dans TA_DIFF_CARTO_LIDAR
ta_bati_carto_single_uniquement_objectid (reader ESRISHAPE_3)
    attributes: FID_CARTO number(11,0)
    -> TA_DIFF_CARTO_LIDAR (writer ORACLE_SPATIAL_5)
TA_DIFF_CARTO_LIDAR (writer ORACLE_SPATIAL_5)
    attributes: OBJECTID number(38,0), FID_LIBELLE number(38,0), ID_CARTO number(38,0), fme_geomattr{7}.oracle_secondary_radius float, fme_geomattr{7}.oracle_start_angle float, fme_geomattr{7}.oracle_rotation float, fme_geomattr{8}.oracle_primary_radius float, fme_geomattr{8}.oracle_rotation float, fme_geomattr{7}.oracle_sweep_angle float, fme_geomattr{8}.oracle_secondary_radius float, fme_geomattr{7}.oracle_primary_radius float
