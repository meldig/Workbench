FME workspace Fusion_Polygones_Ilot.fmw

Parameters:
- SourceDataset_ORACLE_SPATIAL = GEO   # Connection
- DestDataset_ORACLE_SPATIAL = GEO   # Connection

Readers:
- ORACLE_SPATIAL_1: ORACLE_SPATIAL from $(SourceDataset_ORACLE_SPATIAL) in EPSG:2154

Writers:
- ORACLE_SPATIAL_2: ORACLE_SPATIAL to $(DestDataset_ORACLE_SPATIAL) in EPSG:2154

Note: Chargement des données oracle / CLA_INU = 213 / GEO_ON_VALIDE = 0
TA_SUR_TOPO_G (reader ORACLE_SPATIAL_1)
    attributes: OBJECTID number(38,0), CLA_INU number(8,0), GEO_REF varchar2(13), GEO_INSEE char(3), GEO_DV date, GEO_DF date, GEO_ON_VALIDE number(1,0), GEO_TEXTE varchar2(2048), GEO_TYPE char(1), GEO_NMN varchar2(20), GEO_DS date, GEO_NMS varchar2(20), GEO_DM date
    -> CRCCalculator
Note: Création d'un identifiant unique par objet (qui s'incrémentera automatiquement lors d'ajout de données)
CRCCalculator
    ALG_CHOICES = MD5
    CRC_ATTR = _crc
    CRC_TYPE = GEOM_ENCODED
    -> AreaGapAndOverlapCleaner
    -> ChangeDetector [ORIGINAL]
Note: Suppression des espaces de 1.15 m maximum entre deux deux objets à fusionner ou dont un point seulement est commun.
AreaGapAndOverlapCleaner
    CLEANING_TOLERANCE = 1.15
    CONNECT_Z_MODE = Ignore
    DEAGGREGATE_INPUT = YES
    FILL_ALL_GAPS = No
    MEASURE_TYPE = Continuous
    MISSING_VAL_MODE = Compute
    PRIORITY_ATTR = OBJECTID
    REPAIR_METHOD = Priority (Edge Preserving)
    REPAIRED -> Dissolver
Note: Fusion des polygones accolés. / Le plus petit polygone prend le CLA_INU du plus grand.
Dissolver
    ACCUM_INPUT_ATTRS = Use Attributes From One Feature
    CLEANING_TOLERANCE = 0.05
    CONNECT_Z_MODE = Ignore
    DEAGGREGATE_INPUT = Yes
    AREA -> GeometryValidator
Note: Vérification de la validité géométrique des polygones issus de la fusion.
GeometryValidator
    ISSUE_ATTR_NAME = _issues
    PRESETS = Custom
    REPAIR = Yes
    RULES = TYPE_REPAIR CONNECT_Z_MODE]IGNORE_Z]ARC_ENDPOINT_TOLERANCE_MODE]Auto]ARC_ENDPOINT_TOLERANCE]<Unused>]FME_CONTROLLER_QUERY_FILE]transformers/dependencies/geometryvalidator/TYPE_REPAIR.fme SURFACE_ORIENTATION  NULL_REMOVAL  SELF_INTERSECTING CHECK_HOLE_TOUCHING_POLYGON]No]CONNECT_Z_MODE_SI]IGNORE_Z]SELF_INTERSECTION_TOLERANCE]Automatic]FME_CONTROLLER_QUERY_FILE]transformers/dependencies/geometryvalidator/SELF_INTERSECTING.fme
    SUMMARY = Detailed
    PASSED -> ChangeDetector [REVISED]
Note: Différenciation entre les polygones issus de la fusion et les polygones originels.
ChangeDetector
    BLANK_AND_MISSING_DIFFER = No
    CHECK_COORDINATE_SYSTEMS = No
    CHECK_TYPES_AND_ENCODINGS = No
    LENIENT_MATCH = Yes
    MATCH = 2D
    MATCHATTRS = _crc
    MATCH_STRATEGY = Match Selected Attributes
    UNCHANGED_OUTPUT = Output Original
    INSERTED -> MAJ_Polygones_fusionnés
Note: Insert de la date et de l'auteur de création pour les polygones issus de la fusion uniquement.
MAJ_Polygones_fusionnés: AttributeManager
    ATTR_TABLE:
      REMOVE _crc
      RENAME_SET_DEFAULT GEO_ON_VALIDE = 0
      SET_TO GEO_DS = @DateTimeNow(local)
      SET_TO GEO_NMS = bjacq
    -> TEST_FUSION_ILOT (writer ORACLE_SPATIAL_2)
Note: Insertion des données issues de la fusion dans la table TEST_FUSION_ILOT du schéma GEO.
TEST_FUSION_ILOT (writer ORACLE_SPATIAL_2)
    attributes: OBJECTID number(38,0), CLA_INU number(8,0), GEO_REF varchar2(13), GEO_INSEE char(3), GEO_DV date, GEO_DF date, GEO_ON_VALIDE number(1,0), GEO_TEXTE varchar2(2048), GEO_TYPE char(1), GEO_NMN varchar2(20), GEO_DS date, GEO_NMS varchar2(20), GEO_DM date
