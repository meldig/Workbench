FME workspace Fusion_Polygones_Bati.fmw

Parameters:
- SourceDataset_ORACLE_SPATIAL_2 = GEO   # Connection
- DestDataset_ORACLE_SPATIAL = GEO   # Connection
- DestDataset_ORACLE_SPATIAL_4 = GEO   # Connection
- SourceDataset_ORACLE_SPATIAL = GEO   # Connection
- SourceDataset_ORACLE_SPATIAL_3 = GEO   # Connection
- SourceDataset_ORACLE_SPATIAL_7 = GEO   # Connection

Readers:
- ORACLE_SPATIAL_1: ORACLE_SPATIAL from $(SourceDataset_ORACLE_SPATIAL_2) in EPSG:2154
- ORACLE_SPATIAL_4: ORACLE_SPATIAL from $(SourceDataset_ORACLE_SPATIAL) in EPSG:2154
- ORACLE_SPATIAL_5: ORACLE_SPATIAL from $(SourceDataset_ORACLE_SPATIAL_3) in EPSG:2154
- ORACLE_SPATIAL_6: ORACLE_SPATIAL from $(SourceDataset_ORACLE_SPATIAL_7) in EPSG:2154

Writers:
- ORACLE_SPATIAL_2: ORACLE_SPATIAL to $(DestDataset_ORACLE_SPATIAL) in EPSG:2154
- ORACLE_SPATIAL_3: ORACLE_SPATIAL to $(DestDataset_ORACLE_SPATIAL_4) in EPSG:2154

LM_COMMUNES (reader ORACLE_SPATIAL_4)
    attributes: OBJECTID number(38,0), INSEE number, NOM varchar2(30), CODE_POSTAL number(5,0), UT varchar2(50), TERRITOIRE varchar2(50), SURFACE number, PERIMETRE number, CCODTER number, NUMCOM char(3), NOM_MINUS varchar2(50), CCODTER_ENM varchar2(4), CCODTER_ENM2 varchar2(4)
    -> SpatialFilter [Filter]
TA_SUR_TOPO_G (reader ORACLE_SPATIAL_1)
    attributes: OBJECTID number(38,0), CLA_INU number(8,0), GEO_REF varchar2(13), GEO_INSEE char(3), GEO_DV date, GEO_DF date, GEO_ON_VALIDE number(1,0), GEO_TEXTE varchar2(2048), GEO_TYPE char(1), GEO_NMN varchar2(20), GEO_DS date, GEO_NMS varchar2(20), GEO_DM date
    -> SpatialFilter [Candidate]
SpatialFilter
    AGGREGATE_HANDLING = Yes
    BASE_TYPE = Multiple Filters
    CURVE_BOUNDARY_RULE_PARAM = Default Rule
    PASS_CRITERIA = Pass Against One Filter
    PREDICATES = INTERSECTS CONTAINS
    USE_BOUNDING_BOX = No
    PASSED -> CRCCalculator
CRCCalculator
    ALG_CHOICES = MD5
    CRC_ATTR = _crc
    CRC_TYPE = GEOM_ENCODED
    -> AreaGapAndOverlapCleaner
    -> ChangeDetector [ORIGINAL]
AreaGapAndOverlapCleaner
    CLEANING_TOLERANCE = 0.1
    CONNECT_Z_MODE = Ignore
    DEAGGREGATE_INPUT = YES
    FILL_ALL_GAPS = No
    MEASURE_TYPE = Continuous
    MISSING_VAL_MODE = Compute
    PRIORITY_ATTR = OBJECTID
    REPAIR_METHOD = Priority (Edge Preserving)
    REPAIRED -> Dissolver
Dissolver
    ACCUM_INPUT_ATTRS = Use Attributes From One Feature
    CLEANING_TOLERANCE = 0.005
    CONNECT_Z_MODE = Ignore
    DEAGGREGATE_INPUT = Yes
    AREA -> GeometryValidator
GeometryValidator
    ISSUE_ATTR_NAME = _issues
    PRESETS = Custom
    REPAIR = Yes
    RULES = TYPE_REPAIR CONNECT_Z_MODE]IGNORE_Z]ARC_ENDPOINT_TOLERANCE_MODE]Auto]ARC_ENDPOINT_TOLERANCE]<Unused>]FME_CONTROLLER_QUERY_FILE]transformers/dependencies/geometryvalidator/TYPE_REPAIR.fme SURFACE_ORIENTATION  NULL_REMOVAL  SELF_INTERSECTING CHECK_HOLE_TOUCHING_POLYGON]No]CONNECT_Z_MODE_SI]IGNORE_Z]SELF_INTERSECTION_TOLERANCE]Automatic]FME_CONTROLLER_QUERY_FILE]transformers/dependencies/geometryvalidator/SELF_INTERSECTING.fme
    SUMMARY = Detailed
    PASSED -> ChangeDetector [REVISED]
ChangeDetector
    BLANK_AND_MISSING_DIFFER = No
    CHECK_COORDINATE_SYSTEMS = No
    CHECK_TYPES_AND_ENCODINGS = No
    LENIENT_MATCH = Yes
    MATCH = 2D
    MATCHATTRS = _crc
    MATCH_STRATEGY = Match Selected Attributes
    UNCHANGED_OUTPUT = Output Original
    INSERTED -> MAJ_Polygones_fusionnés
    DELETED -> DatabaseUpdater
MAJ_Polygones_fusionnés: AttributeManager
    ATTR_TABLE:
      REMOVE _crc
      RENAME_SET_DEFAULT GEO_ON_VALIDE = 0
      SET_TO GEO_DS = @DateTimeNow(local)
      SET_TO GEO_NMS = bjacq
    -> TA_SUR_TOPO_G (writer ORACLE_SPATIAL_3)
TA_SUR_TOPO_G (writer ORACLE_SPATIAL_3)
    attributes: OBJECTID number(38,0), CLA_INU number(8,0), GEO_REF varchar2(13), GEO_INSEE char(3), GEO_DV date, GEO_DF date, GEO_ON_VALIDE number(1,0), GEO_TEXTE varchar2(2048), GEO_TYPE char(1), GEO_NMN varchar2(20), GEO_DS date, GEO_NMS varchar2(20), GEO_DM date
DatabaseUpdater
    COLUMN_MAP = GEO_ON_VALIDE;1;GEO_NMN;bjacq;GEO_DM;@DateTimeNow(local)
    CONDITION = Match Column(s)
    DATASET = GEO
    EXPOSED_COLUMNS = OBJECTID,GEO_ON_VALIDE,GEO_NMN,GEO_DM
    FORMAT = ORACLE_SPATIAL
    MATCH_COLUMNS = OBJECTID;@Value(OBJECTID)
    ORACLE_SPATIAL_CREATE_FEATURE_TABLES_FROM_DATA = Yes
    ORACLE_SPATIAL_NAMED_CONNECTION = GEO
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = NO
    ORACLE_SPATIAL_USE_UNIFIED_DATE_ATTRS = YES
    TABLE = GEO.TA_SUR_TOPO_G
ZONE_FUSION_BATI (reader ORACLE_SPATIAL_6) [off]
    attributes: OBJECTID number(38,0), GEO_DS date, GEO_NMS varchar2(20)
    -> SpatialFilter_2 [Filter]
TA_SUR_TOPO_G (reader ORACLE_SPATIAL_5) [off]
    attributes: OBJECTID number(38,0), CLA_INU number(8,0), GEO_REF varchar2(13), GEO_INSEE char(3), GEO_DV date, GEO_DF date, GEO_ON_VALIDE number(1,0), GEO_TEXTE varchar2(2048), GEO_TYPE char(1), GEO_NMN varchar2(20), GEO_DS date, GEO_NMS varchar2(20), GEO_DM date
    -> SpatialFilter_2 [Candidate]
SpatialFilter_2
    AGGREGATE_HANDLING = Yes
    BASE_TYPE = Multiple Filters
    CURVE_BOUNDARY_RULE_PARAM = Default Rule
    PASS_CRITERIA = Pass Against One Filter
    PREDICATES = INTERSECTS CONTAINS
    USE_BOUNDING_BOX = No
TEST_FUSION_BATI (writer ORACLE_SPATIAL_2) [off]
    attributes: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

Bookmark: Chargement des bâtis et bâtis secondaires par commune
Note: Chargement de la commune cible.
Note: Chargement des bâtis et bâtis secondaires oracle / CLA_INU = 206 ou 806 / GEO_ON_VALIDE = 0

Bookmark: Chargement des bâtis et bâtis secondaires par zone
Note: Chargement de la zone cible.
Note: Chargement des bâtis et bâtis secondaires oracle / CLA_INU = 206 ou 806 / GEO_ON_VALIDE = 0

Bookmark: Création automatique d'un identifant / objet
Note: Création d'un identifiant unique par objet (qui s'incrémentera automatiquement lors d'ajout de données).

Bookmark: Comblement des espaces entre polygones adjacents + fusion des polygones accolés
Note: Suppression des espaces de 10 cm maximum entre deux deux objets à fusionner ou dont un point seulement est commun.
Note: Fusion des polygones accolés. / Le plus petit polygone prend le CLA_INU du plus grand.
Note: Vérification de la validité géométrique des polygones issus de la fusion.

Bookmark: Distinction des polygones à insérer, à mettre à jour ou à créer
Note: Différenciation entre les polygones issus de la fusion et les polygones originels.
Note: Insertion de la date et du nom du créateur des polygones issus de la fusion uniquement.

Bookmark: Insertion et mise à jour dans les tables oracles
Note: Insertion des données issues de la fusion dans la table TEST_FUSION_BATI du schéma GEO.
Note: Insertion des données issues de la fusion dans la table TA_SUR_TOPO_G du schéma GEO.
Note: Désactivation des polygones ayant servi à la fusion : GEO_ON_VALIDE = 1.
