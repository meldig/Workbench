FME workspace conversion_version_autocad.fmw

Parameters:
- CHOICE = Release2010
- SourceDataset_ACAD =   # Fichier(s) source Autodesk AutoCAD DWG/DXF 
- DestDataset_ACAD = $(FME_MF_DIR_USERTYPED)\resultat   # Fichiers de destination Autodesk AutoCAD DWG/DXF 
- destDir = $(FME_MF_DIR_USERTYPED)\resultat   # Répertoire de sorti

Readers:
- ACAD_1: ACAD from $(SourceDataset_ACAD)

Writers:
- ACAD_2: ACAD to $(DestDataset_ACAD)

0 (reader ACAD_1)
    -> AttributeExposer
Note: Exposition du chemin du fichier
AttributeExposer
    ATTR_LIST = autocad_source_filename,autocad_layer,fme_feature_type
    -> FilenamePartExtractor
Note: Connaitre le nom et l'extension du fichier
FilenamePartExtractor
    DIRNAME_ATTR = _dirname
    DIRPATH_ATTR = _dirpath
    EXTENSION_ATTR = _extension
    FULLNAME_ATTR = _filename
    ROOTNAME_ATTR = _rootname
    SRC_ATTR = @Value(autocad_source_filename)
    -> AttributeCreator
Note: Création d'un nouveau de fichier par concaténation: / - du nom du fichier / - sa nouvelle version / - son extension
AttributeCreator
    ATTR_TABLE = SET_TO nom_fichier = @Value(_rootname)_$(VERSION_SORTIE_FICHIER_AUTOCAD).@Value(_extension)
    -> Couche1 (writer ACAD_2)
Couche1 (writer ACAD_2)
