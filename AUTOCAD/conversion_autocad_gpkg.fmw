FME workspace conversion_autocad_gpkg.fmw

Parameters:
- DestDataset_OGCGEOPACKAGE = $(FME_MF_DIR_USERTYPED)\resultat   # GeoPackage File
- DestDataset_ACAD = $(FME_MF_DIR_USERTYPED)\resultat   # Fichiers de destination Autodesk AutoCAD DWG/DXF 
- SourceDataset_ACAD = $(FME_MF_DIR)test_extrait L93.dwg   # Fichier(s) source Autodesk AutoCAD DWG/DXF 

Readers:
- ACAD_1: ACAD from $(SourceDataset_ACAD)

Writers:
- ACAD_2: ACAD to $(DestDataset_ACAD)
- OGCGEOPACKAGE_1: OGCGEOPACKAGE to $(DestDataset_OGCGEOPACKAGE)

0 (reader ACAD_1)
    -> AttributeExposer
Note: Exposition du chemin du fichier
AttributeExposer
    ATTR_LIST = autocad_source_filename,autocad_layer
    -> FilenamePartExtractor
Note: Connaitre le nom et l'extension du fichier
FilenamePartExtractor
    DIRNAME_ATTR = _dirname
    DIRPATH_ATTR = _dirpath
    EXTENSION_ATTR = _extension
    FULLNAME_ATTR = _filename
    ROOTNAME_ATTR = _rootname
    SRC_ATTR = @Value(autocad_source_filename)
    -> AttributeCreator_8
Note: Création de l'attribut du nom_fichier.
AttributeCreator_8
    ATTR_TABLE = SET_TO nom_fichier = @Value(_rootname).gpkg
    -> Table1 (writer OGCGEOPACKAGE_1)
Table1 (writer OGCGEOPACKAGE_1)
    attributes: autocad_source_filename text(200)
