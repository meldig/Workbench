FME workspace conversion_reprojection_autocad.fmw

Parameters:
- SRC_SYSTEME = EPSG:2154   # Systeme de coordonné en entré
- DEST_SYSTEME = EPSG:4326   # Système de coordonné en sorti
- SourceDataset_ACAD = $(FME_MF_DIR)extrait L93.dwg   # Fichier(s) source Autodesk AutoCAD DWG/DXF 
- DestDataset_ACAD = $(FME_MF_DIR_USERTYPED)\resultat   # Fichiers de destination Autodesk AutoCAD DWG/DXF 

Readers:
- ACAD_1: ACAD from $(SourceDataset_ACAD)

Writers:
- ACAD_2: ACAD to $(DestDataset_ACAD)

0 (reader ACAD_1)
    -> AttributeExposer
Note: Exposition du chemin du fichier
AttributeExposer
    ATTR_LIST = autocad_source_filename,autocad_layer
    -> FilenamePartExtractor
Note: Connaitre le nom et l'extension du fichier
FilenamePartExtractor
    DIRNAME_ATTR = _dirname
    DIRPATH_ATTR = _dirpath
    EXTENSION_ATTR = _extension
    FULLNAME_ATTR = _filename
    ROOTNAME_ATTR = _rootname
    SRC_ATTR = @Value(autocad_source_filename)
    -> Reprojector
Note: Reprojection
Reprojector
    DEST = $(DEST_SYSTEME)
    INTERPOLATION_TYPE_NAME = Nearest Neighbor
    RASTER_CELL_SIZE = Preserve Cells
    RASTER_TOLERANCE = 0.0
    SOURCE = $(SRC_SYSTEME)
    REPROJECTED -> AttributeCreator_8
Note: Création de l'attribut du nom_fichier.
AttributeCreator_8
    ATTR_TABLE = SET_TO nom_fichier = @Value(_rootname)_reprojection_@ReplaceString($(DEST_SYSTEME),:,_).@Value(_extension)
    -> 0 (writer ACAD_2)
0 (writer ACAD_2)
