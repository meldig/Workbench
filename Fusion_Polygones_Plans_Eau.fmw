FME workspace Fusion_Polygones_Plans_Eau.fmw

Parameters:
- SourceDataset_ORACLE_SPATIAL_2 = GEO   # Connection
- DestDataset_ORACLE_SPATIAL_3 = GEO   # Connection

Readers:
- ORACLE_SPATIAL_3: ORACLE_SPATIAL from $(SourceDataset_ORACLE_SPATIAL_2) in EPSG:2154

Writers:
- ORACLE_SPATIAL_1: ORACLE_SPATIAL to $(DestDataset_ORACLE_SPATIAL_3) in EPSG:2154

TA_SUR_TOPO_G (reader ORACLE_SPATIAL_3)
    attributes: OBJECTID number(38,0), CLA_INU number(8,0), GEO_REF varchar2(13), GEO_INSEE char(3), GEO_DV date, GEO_DF date, GEO_ON_VALIDE number(1,0), GEO_TEXTE varchar2(2048), GEO_TYPE char(1), GEO_NMN varchar2(20), GEO_DS date, GEO_NMS varchar2(20), GEO_DM date
    -> CRCCalculator
CRCCalculator
    ALG_CHOICES = MD5
    CRC_ATTR = _crc
    CRC_TYPE = GEOM_ENCODED
    -> AreaGapAndOverlapCleaner
    -> ChangeDetector [ORIGINAL]
AreaGapAndOverlapCleaner
    CLEANING_TOLERANCE = 0.4
    CONNECT_Z_MODE = Ignore
    DEAGGREGATE_INPUT = YES
    FILL_ALL_GAPS = No
    MEASURE_TYPE = Continuous
    MISSING_VAL_MODE = Compute
    PRIORITY_ATTR = OBJECTID
    REPAIR_METHOD = Priority (Edge Preserving)
    REPAIRED -> Dissolver
Dissolver
    ACCUM_INPUT_ATTRS = Use Attributes From One Feature
    CLEANING_TOLERANCE = 0
    CONNECT_Z_MODE = Ignore
    DEAGGREGATE_INPUT = Yes
    AREA -> GeometryValidator
GeometryValidator
    ISSUE_ATTR_NAME = _issues
    PRESETS = Custom
    REPAIR = Yes
    RULES = TYPE_REPAIR CONNECT_Z_MODE]IGNORE_Z]ARC_ENDPOINT_TOLERANCE_MODE]Auto]ARC_ENDPOINT_TOLERANCE]<Unused>]FME_CONTROLLER_QUERY_FILE]transformers/dependencies/geometryvalidator/TYPE_REPAIR.fme SURFACE_ORIENTATION  NULL_REMOVAL  SELF_INTERSECTING CHECK_HOLE_TOUCHING_POLYGON]No]CONNECT_Z_MODE_SI]IGNORE_Z]SELF_INTERSECTION_TOLERANCE]Automatic]FME_CONTROLLER_QUERY_FILE]transformers/dependencies/geometryvalidator/SELF_INTERSECTING.fme
    SUMMARY = Detailed
    PASSED -> ChangeDetector [REVISED]
ChangeDetector
    BLANK_AND_MISSING_DIFFER = No
    CHECK_COORDINATE_SYSTEMS = No
    CHECK_TYPES_AND_ENCODINGS = No
    LENIENT_MATCH = Yes
    MATCH = 2D
    MATCHATTRS = _crc
    MATCH_STRATEGY = Match Selected Attributes
    UNCHANGED_OUTPUT = Output Original
    INSERTED -> MAJ_Polygones_fusionnés
    DELETED -> DatabaseUpdater
MAJ_Polygones_fusionnés: AttributeManager
    ATTR_TABLE:
      REMOVE _crc
      RENAME_SET_DEFAULT CLA_INU = 325
      RENAME_SET_DEFAULT GEO_ON_VALIDE = 0
      SET_TO GEO_DS = @DateTimeNow(local)
      SET_TO GEO_NMS = bjacq
    -> TA_SUR_TOPO_G (writer ORACLE_SPATIAL_1)
TA_SUR_TOPO_G (writer ORACLE_SPATIAL_1)
    attributes: OBJECTID number(38,0), CLA_INU number(8,0), GEO_REF varchar2(13), GEO_INSEE char(3), GEO_DV date, GEO_DF date, GEO_ON_VALIDE number(1,0), GEO_TEXTE varchar2(2048), GEO_TYPE char(1), GEO_NMN varchar2(20), GEO_DS date, GEO_NMS varchar2(20), GEO_DM date
DatabaseUpdater
    COLUMN_MAP = GEO_ON_VALIDE;1;GEO_NMN;bjacq;GEO_DM;@DateTimeNow(local)
    CONDITION = Match Column(s)
    DATASET = GEO
    EXPOSED_COLUMNS = OBJECTID,GEO_ON_VALIDE,GEO_NMN,GEO_DM
    FORMAT = ORACLE_SPATIAL
    MATCH_COLUMNS = OBJECTID;@Value(OBJECTID);CLA_INU;325
    ORACLE_SPATIAL_CREATE_FEATURE_TABLES_FROM_DATA = Yes
    ORACLE_SPATIAL_NAMED_CONNECTION = GEO
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = NO
    ORACLE_SPATIAL_USE_UNIFIED_DATE_ATTRS = YES
    TABLE = GEO.TA_SUR_TOPO_G
