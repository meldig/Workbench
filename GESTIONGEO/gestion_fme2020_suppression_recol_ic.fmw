FME workspace gestion_fme2020_suppression_recol_ic.fmw

Parameters:
- NUMERO_DOSSIER =   # NUMERO DOSSIER
- TYPE_SUPPRESSION =   # SUPPRESSION COMPLETE DU DOSSIER,1%SUPPRESSION DES ELEMENTS TOPOGRAPHIQUE DU DOSSIER,2 TYPE DE SUPPRESSION
- INSTANCE_PRODUCTION_ORACLE_12_C =   # INSTANCE PRODUCTION ORACLE 12 C
- INSTANCE_PRODUCTION_ORACLE_11_G =   # INSTANCE PRODUCTION ORACLE 11 G
- UTILISATEUR_G_GESTIONGEO_MAJ = G_GESTIONGEO_MAJ   # UTILISATEUR G_GESTIONGEO MAJ
- UTILISATEUR_G_GESTIONGEO_LEC = G_GESTIONGEO_LEC   # UTILISATEUR G_GESTIONGEO_LEC
- UTILISATEUR_G_GESTIONGEO = G_GESTIONGEO   # UTILISATEUR G_GSTIONGEO
- UTILISATEUR_GEO = GEO   # UTILISATEUR GEO
- MDP_PRODUCTION_INSTANCE_ORACKE_11_C_SCHEMA_GEO =   # MDP PRODUCTION INSTANCE 11 C SCHEMA GEO
- MDP_PRODUCTION_INSTANCE_ORACLE_12_C_SCHEMA_G_GESTIONGEO_MAJ =   # MDP PRODUCTION INSTANCE ORACLE 12 C SCHEMA G_GESTIONGEO_MAJ
- MDP_PRODUCTION_INSTANCE_ORACLE_12_C_SCEMA_G_GESTIONGEO_LEC =   # MDP PRODUCTION INSTANCE ORACLE 12 C SCHEMA G_GESTIONGEO_LEC
- TA_POINT_TOPO_GPS = TA_POINT_TOPO_GPS   # TABLE TA_POINT_TOPO_GPS
- TA_LIG_TOPO_GPS = TA_LIG_TOPO_GPS   # TABLE TA_LIG_TOPO_GPS
- TA_GG_DOSSIER = TA_GG_DOSSIER   # TABLE TA_GG_DOSSIER
- TA_GG_GEO = TA_GG_GEO   # TABLE TA_GG_GEO
- TA_GG_FICHIER = TA_GG_FICHIER   # TABLE TA_GG_FICHIER
- PTTOPO = PTTOPO   # TABLE DES POINTS PTTOPO

Readers:
- ORACLE_AUTONOMOUS_NONSPATIAL_1: ORACLE_AUTONOMOUS_NONSPATIAL from $(INSTANCE_PRODUCTION_ORACLE_12_C)

Creator
    GEOMTYPE = Geometry Object
    NUM = 1
    CREATED -> AttributeCreator
Note: Creation de l'attribut NUMERO_DOSSIER
AttributeCreator
    ATTR_TABLE = SET_TO NUMERO_DOSSIER = $(NUMERO_DOSSIER)
    -> Tester
Note: Aiguillage seleon le type de suppression: / 1: Suppression compléte du dossier / 2: Suppression des élements topographiques du dossier. / TYPE de suppression = 1
Tester
    BOOL_OP = OR
    COMPOSITE_TEST = 1
    TEST_CLAUSE = TEST $(TYPE_SUPPRESSION) = 1
    TEST_MODE = TEST
    PASSED -> SQLExecutor_5 [INITIATOR]
    PASSED -> SQLExecutor_4 [INITIATOR]
    PASSED -> SQLExecutor_3 [INITIATOR]
    PASSED -> SQLExecutor_2 [INITIATOR]
    FAILED -> SQLExecutor_2 [INITIATOR]
    FAILED -> SQLExecutor_3 [INITIATOR]
    FAILED -> SQLExecutor_4 [INITIATOR]

Bookmark: Suppression des éléments du dossier contenus dans le schéma GEO@CUDLT
Note: Suppression des elements du dossier dans GEO.TA_POINT_TOPO_GPS
SQLExecutor_2
    COMBINE_ATTRS = Result Attributes Only
    COMBINE_GEOM = Initiator Geometry Only
    DATASET = $(INSTANCE_PRODUCTION_ORACLE_11_G)
    FORMAT = ORACLE_SPATIAL
    ORACLE_SPATIAL_CREATE_FEATURE_TABLES_FROM_DATA = Yes
    ORACLE_SPATIAL_PASSWORD = $(MDP_PRODUCTION_INSTANCE_ORACKE_11_C_SCHEMA_GEO)
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = NO
    ORACLE_SPATIAL_USER_NAME = $(UTILISATEUR_GEO)
    ORACLE_SPATIAL_USE_UNIFIED_DATE_ATTRS = YES
    SQL_STATEMENT:
      DELETE
      FROM
      $(UTILISATEUR_GEO).$(TA_POINT_TOPO_GPS)
      WHERE
      GEO_REF = 'REC_$(NUMERO_DOSSIER)'
    INITIATOR -> AttributeKeeper_2
Note: Suppression des elements du dossier dans GEO.TEMP_TA_LIG_TOPO_GPS
SQLExecutor_3
    COMBINE_ATTRS = Result Attributes Only
    COMBINE_GEOM = Initiator Geometry Only
    DATASET = $(INSTANCE_PRODUCTION_ORACLE_11_G)
    FORMAT = ORACLE_SPATIAL
    ORACLE_SPATIAL_CREATE_FEATURE_TABLES_FROM_DATA = Yes
    ORACLE_SPATIAL_PASSWORD = $(MDP_PRODUCTION_INSTANCE_ORACKE_11_C_SCHEMA_GEO)
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = NO
    ORACLE_SPATIAL_USER_NAME = $(UTILISATEUR_GEO)
    ORACLE_SPATIAL_USE_UNIFIED_DATE_ATTRS = YES
    SQL_STATEMENT:
      DELETE
      FROM
      $(UTILISATEUR_GEO).$(TA_LIG_TOPO_GPS)
      WHERE
      GEO_REF = 'REC_$(NUMERO_DOSSIER)'
    INITIATOR -> AttributeKeeper_2
Note: Suppression des elements du dossier dans GEO.PTTOPO
SQLExecutor_4
    COMBINE_ATTRS = Result Attributes Only
    COMBINE_GEOM = Initiator Geometry Only
    DATASET = $(INSTANCE_PRODUCTION_ORACLE_11_G)
    FORMAT = ORACLE_SPATIAL
    ORACLE_SPATIAL_CREATE_FEATURE_TABLES_FROM_DATA = Yes
    ORACLE_SPATIAL_PASSWORD = $(MDP_PRODUCTION_INSTANCE_ORACKE_11_C_SCHEMA_GEO)
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = NO
    ORACLE_SPATIAL_USER_NAME = $(UTILISATEUR_GEO)
    ORACLE_SPATIAL_USE_UNIFIED_DATE_ATTRS = YES
    SQL_STATEMENT:
      DELETE
      FROM
      $(UTILISATEUR_GEO).$(PTTOPO)
      WHERE
      ID_DOS = $(NUMERO_DOSSIER)
    INITIATOR -> AttributeKeeper_2

Bookmark: Suppression des éléments du dossier contenues dans le schéma G_GESTIONGEO@MULTIT
Note: Suppression des lignes du dossier de la table TA_GG_FICHIER
SQLExecutor_5
    COMBINE_ATTRS = Result Attributes Only
    COMBINE_GEOM = Initiator Geometry Only
    DATASET = $(INSTANCE_PRODUCTION_ORACLE_12_C)
    FORMAT = ORACLE_SPATIAL
    ORACLE_SPATIAL_CREATE_FEATURE_TABLES_FROM_DATA = Yes
    ORACLE_SPATIAL_PASSWORD = $(MDP_PRODUCTION_INSTANCE_ORACLE_12_C_SCHEMA_G_GESTIONGEO_MAJ)
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = NO
    ORACLE_SPATIAL_USER_NAME = $(UTILISATEUR_G_GESTIONGEO_MAJ)
    ORACLE_SPATIAL_USE_UNIFIED_DATE_ATTRS = YES
    SQL_STATEMENT:
      DELETE
      FROM
      $(UTILISATEUR_G_GESTIONGEO).$(TA_GG_FICHIER)
      WHERE
      FID_DOSSIER = $(NUMERO_DOSSIER)
    INITIATOR -> DatabaseJoiner
Note: Cette jointure permet de recupérer le FID_PERIMETRE d'un dossier pour supprimer sa ligne dans la table TA_GG_GEO.
DatabaseJoiner
    ADDED_FIELDS = FID_PERIMETRE
    ATTR_ACCUM_MODE = Merge Joined
    ATTR_CONFLICT_RES = Use Joined
    CACHE_SIZE = 5000
    DATASET = $(INSTANCE_PRODUCTION_ORACLE_12_C)
    FORMAT = ORACLE_SPATIAL
    JOIN_KEYS = NUMERO_DOSSIER OBJECTID
    MATCH_RULE_DISPLAY = Must Match Exactly One (1:1)
    ORACLE_SPATIAL_CREATE_FEATURE_TABLES_FROM_DATA = Yes
    ORACLE_SPATIAL_PASSWORD = $(MDP_PRODUCTION_INSTANCE_ORACLE_12_C_SCHEMA_G_GESTIONGEO_MAJ)
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = NO
    ORACLE_SPATIAL_USER_NAME = $(UTILISATEUR_G_GESTIONGEO_MAJ)
    ORACLE_SPATIAL_USE_UNIFIED_DATE_ATTRS = YES
    PREFETCH_EXHAUSTIVE = Yes
    TABLE = $(UTILISATEUR_G_GESTIONGEO).$(TA_GG_DOSSIER)
    JOINED -> SQLExecutor_8 [INITIATOR]
Note: Suppression du dossier dans TA_GG_DOSSIER
SQLExecutor_8
    COMBINE_ATTRS = Result Attributes Only
    COMBINE_GEOM = Initiator Geometry Only
    DATASET = $(INSTANCE_PRODUCTION_ORACLE_12_C)
    FORMAT = ORACLE_SPATIAL
    ORACLE_SPATIAL_CREATE_FEATURE_TABLES_FROM_DATA = Yes
    ORACLE_SPATIAL_PASSWORD = $(MDP_PRODUCTION_INSTANCE_ORACLE_12_C_SCHEMA_G_GESTIONGEO_MAJ)
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = NO
    ORACLE_SPATIAL_USER_NAME = $(UTILISATEUR_G_GESTIONGEO_MAJ)
    ORACLE_SPATIAL_USE_UNIFIED_DATE_ATTRS = YES
    SQL_STATEMENT:
      DELETE
      FROM
      $(UTILISATEUR_G_GESTIONGEO).$(TA_GG_DOSSIER)
      WHERE
      OBJECTID = $(NUMERO_DOSSIER)
    INITIATOR -> SQLExecutor [INITIATOR]
Note: Suppression du dossier dans TA_GG_GEO
SQLExecutor
    COMBINE_ATTRS = Result Attributes Only
    COMBINE_GEOM = Initiator Geometry Only
    DATASET = $(INSTANCE_PRODUCTION_ORACLE_12_C)
    FORMAT = ORACLE_SPATIAL
    ORACLE_SPATIAL_CREATE_FEATURE_TABLES_FROM_DATA = Yes
    ORACLE_SPATIAL_PASSWORD = $(MDP_PRODUCTION_INSTANCE_ORACLE_12_C_SCHEMA_G_GESTIONGEO_MAJ)
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = NO
    ORACLE_SPATIAL_USER_NAME = $(UTILISATEUR_G_GESTIONGEO_MAJ)
    ORACLE_SPATIAL_USE_UNIFIED_DATE_ATTRS = YES
    SQL_STATEMENT:
      DELETE
      FROM
      $(UTILISATEUR_G_GESTIONGEO).$(TA_GG_GEO)
      WHERE
      OBJECTID = @Value(FID_PERIMETRE)
    INITIATOR -> AttributeKeeper_2

Bookmark: Suppression du repertoire du dossier
Note: On garde l'attribut du numero de dossier qui est la seule information utile pour la suite du traitement.
AttributeKeeper_2
    CREATE_BULK_MODE_FEATURES = NO
    KEEP_ATTRS = NUMERO_DOSSIER
    -> Aggregator
Note: Aggrégation de l'attribut pour n'avoir qu'une ligne
Aggregator
    ACCUM_ATTRS_NAME = Merge Incoming Attributes
    MODE = Attributes Only
    SEP = ,
    AGGREGATE -> Tester_2
Note: Aiguillage seleon le type de suppression: / 1: Suppression compléte du dossier / 2: Mise à 0 de l'attribut du fichier intégré.
Tester_2
    BOOL_OP = OR
    COMPOSITE_TEST = 1
    TEST_CLAUSE = TEST $(TYPE_SUPPRESSION) = 1
    TEST_MODE = TEST
    PASSED -> FeatureMerger [SUPPLIER]
    FAILED -> FeatureMerger_2 [REQUESTOR]
V_VALEUR_GESTION_TRAITEMENT_FME (reader ORACLE_AUTONOMOUS_NONSPATIAL_1)
    attributes: REPERTOIRE varchar2(4000), ETAT_ID_FINAL_RECOL number(38,0), ETAT_ID_FINAL_IC number(38,0), ETAT_ID_MAJ number(38,0)
    -> AttributeKeeper_3
    -> AttributeKeeper_4
Note: On garde l'atribut REPERTOIRE pour reconstituer le nom du dossier à supprimer
AttributeKeeper_3
    CREATE_BULK_MODE_FEATURES = NO
    KEEP_ATTRS = REPERTOIRE
    -> FeatureMerger [REQUESTOR]
Note: jointure pour recomposer le chemin du dossier à supprimer.
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> AttributeCreator_2
Note: Creation du chemin du dossier
AttributeCreator_2
    ATTR_TABLE = SET_TO chemin_dossier = @Value(REPERTOIRE)/$(NUMERO_DOSSIER)
    -> SystemCaller
Note: Suppression du répertoire du dossier a l'aide d'une commande DOS RMDIR
SystemCaller
    CMD = rm -r @Value(chemin_dossier)
Note: On garde l'atribut ETAT_ID_MAJ pour mettre à jour le champ FID_ETAT_AVANCEMENT de la table TA_GG_DOSSIER
AttributeKeeper_4
    CREATE_BULK_MODE_FEATURES = NO
    KEEP_ATTRS = ETAT_ID_MAJ
    -> FeatureMerger_2 [SUPPLIER]
Note: jointure pour recomposer le chemin du dossier à supprimer.
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> SQLExecutor_6 [INITIATOR]
Note: Instruction pour récupérer le chemin du dernier fichier intégré du dossier dans la table TA_GG_FICHIER
SQLExecutor_6
    COMBINE_ATTRS = Result Attributes Only
    COMBINE_GEOM = Initiator Geometry Only
    DATASET = $(INSTANCE_PRODUCTION_ORACLE_12_C)
    EXPOSED_ATTRIBUTE_LIST = OBJECTID
    FORMAT = ORACLE_AUTONOMOUS_NONSPATIAL
    ORACLE_AUTONOMOUS_NONSPATIAL_CREATE_FEATURE_TABLES_FROM_DATA = Yes
    ORACLE_AUTONOMOUS_NONSPATIAL_PASSWORD = $(MDP_PRODUCTION_INSTANCE_ORACLE_12_C_SCEMA_G_GESTIONGEO_LEC)
    ORACLE_AUTONOMOUS_NONSPATIAL_PERSISTENT_CONNECTION = YES
    ORACLE_AUTONOMOUS_NONSPATIAL_QUERY_FEATURE_TYPES_FOR_MERGE_FILTERS = Yes
    ORACLE_AUTONOMOUS_NONSPATIAL_REMOVE_SCHEMA_QUALIFIER = NO
    ORACLE_AUTONOMOUS_NONSPATIAL_SERVER_TYPE = ORACLE8i
    ORACLE_AUTONOMOUS_NONSPATIAL_SHOW_SYSTEM_TABLES = NO
    ORACLE_AUTONOMOUS_NONSPATIAL_USER_NAME = $(UTILISATEUR_G_GESTIONGEO_LEC)
    ORACLE_AUTONOMOUS_NONSPATIAL_USE_UNIFIED_DATE_ATTRS = YES
    SQL_STATEMENT:
      SELECT
          OBJECTID,
          FICHIER
      FROM
          $(UTILISATEUR_G_GESTIONGEO).$(TA_GG_FICHIER)
      WHERE
          FID_DOSSIER = $(NUMERO_DOSSIER)
      AND
          INTEGRATION = 1
    RESULT -> SQLExecutor_7 [INITIATOR]
Note: Mise à jour de la liigne du dernier fichier intégré dans la table TA_GG_FICHIER
SQLExecutor_7
    COMBINE_ATTRS = Result Attributes Only
    COMBINE_GEOM = Initiator Geometry Only
    DATASET = $(INSTANCE_PRODUCTION_ORACLE_12_C)
    FORMAT = ORACLE_SPATIAL
    ORACLE_SPATIAL_CREATE_FEATURE_TABLES_FROM_DATA = Yes
    ORACLE_SPATIAL_PASSWORD = $(MDP_PRODUCTION_INSTANCE_ORACLE_12_C_SCHEMA_G_GESTIONGEO_MAJ)
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = NO
    ORACLE_SPATIAL_USER_NAME = $(UTILISATEUR_G_GESTIONGEO_MAJ)
    ORACLE_SPATIAL_USE_UNIFIED_DATE_ATTRS = YES
    SQL_STATEMENT:
      UPDATE
      $(UTILISATEUR_G_GESTIONGEO).$(TA_GG_FICHIER)
      SET INTEGRATION = 0
      WHERE OBJECTID = @Value(OBJECTID)
    INITIATOR -> DatabaseUpdater
Note: Mise a jour de l'etat du dossier en attent de levé géomètre.
DatabaseUpdater
    COLUMN_MAP = FID_ETAT_AVANCEMENT;ETAT_ID_MAJ
    CONDITION = Match Column(s)
    DATASET = $(INSTANCE_PRODUCTION_ORACLE_12_C)
    EXPOSED_COLUMNS = OBJECTID,FID_ETAT_AVANCEMENT,FID_FAMILLE,FID_PERIMETRE,FID_PNOM_CREATION,FID_PNOM_MODIFICATION,DATE_SAISIE,DATE_MODIFICATION,DATE_CLOTURE,DATE_DEBUT_LEVE,DATE_FIN_LEVE,DATE_DEBUT_TRAVAUX,DATE_FIN_TRAVAUX,DATE_COMMANDE_DOSSIER,MAITRE_OUVRAGE,RESPONSABLE_LEVE,ENTREPRISE_TRAVAUX,REMARQUE_GEOMETRE,REMARQUE_PHOTO_INTERPRETE
    FORMAT = ORACLE_NONSPATIAL
    MATCH_COLUMNS = OBJECTID;$(NUMERO_DOSSIER)
    ORACLE_NONSPATIAL_CREATE_FEATURE_TABLES_FROM_DATA = Yes
    ORACLE_NONSPATIAL_PASSWORD = $(MDP_PRODUCTION_INSTANCE_ORACLE_12_C_SCHEMA_G_GESTIONGEO_MAJ)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(UTILISATEUR_G_GESTIONGEO_MAJ)
    ORACLE_NONSPATIAL_USE_UNIFIED_DATE_ATTRS = YES
    TABLE = G_GESTIONGEO.TA_GG_DOSSIER
