FME workspace gestion_fme2020_deplacement_recol_ic.fmw

Parameters:
- TEXT =   # NUMERO_DOSSIER NUMERO DU DOSSIER ASSOCIE AU FICHIER
- FILENAME_MUSTEXIST =   # FICHIER_A_DEPLACER *|* FICHIER A DEPLACER
- INSTANCE_PRODUCTION_ORACLE_12_C =   # INSTANCE PRODUCTION ORACLE 12 C
- UTILISATEUR_G_GESTIONGEO_LEC = G_GESTIONGEO_LEC   # UTILISATEURG_GESTIONGEO_LEC
- UTILISATEUR_G_GESTIONGEO = G_GESTIONGEO   # UTILISATEUR G_GESTIONGEO
- MDP_PRODUCTION_INSTANCE_ORACLE_12_C_SCHEMA_G_GESTIONGEO_LEC =   # MDP PRODUCTION INSTANCE ORACLE 12 C SCHEMA G_GESTIONGEO_LEC
- TA_GG_FICHIER = TA_GG_FICHIER   # TABLE_TA_GG_FICHIER
- TA_GG_GEO = TA_GG_GEO   # TABLE TA_GG_GEO
- SCHEMAC_G_GESTIONGEO_TABLE_TA_GG_GEO = G_GESTIONGEO.TA_GG_GEO
- REPERTOIRE = @Value(REPERTOIRE)

Readers:
- ORACLE_AUTONOMOUS_NONSPATIAL_1: ORACLE_AUTONOMOUS_NONSPATIAL from $(INSTANCE_PRODUCTION_ORACLE_12_C)
- ORACLE_AUTONOMOUS_NONSPATIAL_2: ORACLE_AUTONOMOUS_NONSPATIAL from $(INSTANCE_PRODUCTION_ORACLE_12_C)
- ORACLE_NONSPATIAL_1: ORACLE_NONSPATIAL from $(INSTANCE_PRODUCTION_ORACLE_12_C)

Writers:
- FILECOPY_1: FILECOPY to $(REPERTOIRE)
- ORACLE_AUTONOMOUS_NONSPATIAL_3: ORACLE_AUTONOMOUS_NONSPATIAL to $(INSTANCE_PRODUCTION_ORACLE_12_C)

V_VALEUR_GESTION_TRAITEMENT_FME (reader ORACLE_NONSPATIAL_1)
    attributes: REPERTOIRE varchar2(4000), ETAT_ID_FINAL_RECOL number(38,0), ETAT_ID_FINAL_IC number(38,0), ETAT_ID_MAJ number(38,0)
    -> AttributeKeeper_4
Note: On ne garde que l'attribut REPERTOIRE pour analyser pouvoir connaitre le dossier dans lequel copier les fichiers associés au dossier et également comparer le fichiers déjà associés à un dossier à celui que l'on souhaite associé.
AttributeKeeper_4
    CREATE_BULK_MODE_FEATURES = NO
    KEEP_ATTRS = REPERTOIRE
    -> FeatureMerger_2 [SUPPLIER]
    -> FeatureMerger [SUPPLIER]

Bookmark: Vérification si des fichiers existe déja en base pour le dossier spécifié
TA_GG_FICHIER (reader ORACLE_AUTONOMOUS_NONSPATIAL_2)
    attributes: OBJECTID number(38,0), FID_DOSSIER number(38,0), FICHIER varchar2(250), INTEGRATION number(1,0)
    -> FeatureMerger [REQUESTOR]
Note: Jointure de l'attribut REPERTOIRE
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> AttributeCreator
Note: Creation de l'élément FICHIER A ANALYSER pour pouvoir comparer la somme des valeurs de controle entre les fichiers déja attachés à un dossier et celui que l'utilisateur veut déplacer.
AttributeCreator
    ATTR_TABLE = SET_TO FICHIER_A_ANALYSER = @Value(REPERTOIRE)/$(NUMERO_DOSSIER)/@Value(FICHIER)
    -> CRCCalculator_2
Note: Calcul la somme des valeurs de controle des fichiers attachés à un dossier déja renseignés en base.
CRCCalculator_2
    ALG_CHOICES = MD5
    CRC_ATTR = CRC_FICHIER_BASE
    CRC_TYPE = FILE
    FILE_NAME = @Value(FICHIER_A_ANALYSER)
    -> AttributeKeeper
Note: Ne garde que la valeur du calcul de somme
AttributeKeeper
    CREATE_BULK_MODE_FEATURES = NO
    KEEP_ATTRS = CRC_FICHIER_BASE
    -> FeatureJoiner [LEFT]

Bookmark: Analyse le fichier qui doit être attaché au dossier spécifé determine ses attributs
Creator
    GEOMTYPE = Geometry Object
    NUM = 1
    CREATED -> AttributeCreator_4
AttributeCreator_4
    ATTR_TABLE = SET_TO fichier_source = $(FICHIER_A_DEPLACER)
    -> FilenamePartExtractor
Note: Extraction du chemin pour determiner le chemin, le nom, l'extension et les caractéristiques du fichier à déplacer.
FilenamePartExtractor
    DIRNAME_ATTR = _dirname
    DIRPATH_ATTR = _dirpath
    EXTENSION_ATTR = _extension
    FULLNAME_ATTR = _filename
    ROOTNAME_ATTR = _rootname
    SRC_ATTR = @Value(fichier_source)
    -> AttributeCreator_2
Note: Création des attribut pour les writers filecopy: / - nom_fichier: nom du fichier de sortir / - chemin_fichier: chemin de sortie du fichier / - source_fichier: fichier original / - DOS_URL_FILE: chemin_fichier/nom_fichier / création de l'attribut FILE_INTEGRATION_TOPO / - 0: fichier attaché au dossier. Mais non intégré
AttributeCreator_2
    ATTR_TABLE:
      SET_TO nom_fichier = @Value(_rootname).@Value(_extension)
      SET_TO INTEGRATION = 0
      SET_TO DOS_URL_FILE = @Value(_rootname).@Value(_extension)
      SET_TO NUMERO_DOSSIER = $(NUMERO_DOSSIER)
    -> CRCCalculator
Note: Calcul la somme des valeurs de controle du fichier qui doit être inséré en base
CRCCalculator
    ALG_CHOICES = MD5
    CRC_ATTR = CRC_FICHIER_INTEGRE
    CRC_TYPE = FILE
    FILE_NAME = $(FICHIER_A_DEPLACER)
    -> FeatureJoiner [RIGHT]

Bookmark: comparaison entre les deux fichiers
Note: compare si le fichier inséré n'est pas déjà présent en base. / Si le fichier n'est pas joint, cela signifie qu'il est différent de ceux déja en base, il va être inséré
FeatureJoiner
    ATTR_CONFLICT_RES = Use Left
    GEOMETRY_HANDLING = Use Left
    JOIN_KEYS = CRC_FICHIER_BASE CRC_FICHIER_INTEGRE AUTO
    JOIN_MODE = Inner
    UNJOINED_RIGHT -> SQLExecutor [INITIATOR]

Bookmark: Creation du nouveau nom du fichier: OBJECTID de sa ligne dans la table TA_GG_FICHIER + NUMERO_DOSSIER + CODE_INSEE + NOM COMMUNE + EXTENSION du fichier
Note: Determine l'objectid du nouvel élément à rajouter dans la table G_GESTIONGEO.TA_GG_FICHIER. MAX(OBJECTID)+1
SQLExecutor
    ATTR_IGNORE_NULLS = No
    COMBINE_ATTRS = Keep Initiator Attributes if Conflict
    COMBINE_GEOM = Initiator Geometry Only
    DATASET = $(INSTANCE_PRODUCTION_ORACLE_12_C)
    EXPOSED_ATTRIBUTE_LIST = OBJECTID_MAX_PLUS_1
    FORMAT = ORACLE_AUTONOMOUS_NONSPATIAL
    ORACLE_AUTONOMOUS_NONSPATIAL_CREATE_FEATURE_TABLES_FROM_DATA = Yes
    ORACLE_AUTONOMOUS_NONSPATIAL_PASSWORD = $(MDP_PRODUCTION_INSTANCE_ORACLE_12_C_SCHEMA_G_GESTIONGEO_LEC)
    ORACLE_AUTONOMOUS_NONSPATIAL_PERSISTENT_CONNECTION = YES
    ORACLE_AUTONOMOUS_NONSPATIAL_QUERY_FEATURE_TYPES_FOR_MERGE_FILTERS = Yes
    ORACLE_AUTONOMOUS_NONSPATIAL_REMOVE_SCHEMA_QUALIFIER = NO
    ORACLE_AUTONOMOUS_NONSPATIAL_SERVER_TYPE = ORACLE8i
    ORACLE_AUTONOMOUS_NONSPATIAL_SHOW_SYSTEM_TABLES = NO
    ORACLE_AUTONOMOUS_NONSPATIAL_USER_NAME = $(UTILISATEUR_G_GESTIONGEO_LEC)
    ORACLE_AUTONOMOUS_NONSPATIAL_USE_UNIFIED_DATE_ATTRS = YES
    SQL_STATEMENT:
      SELECT
          CASE
              WHEN max(objectid) IS NULL THEN 1
              ELSE max(objectid) + 1
          END OBJECTID_MAX_PLUS_1
      FROM
          $(UTILISATEUR_G_GESTIONGEO).$(TA_GG_FICHIER)
    RESULT -> FeatureJoiner_3 [RIGHT]
Note: joint au fichier le code insee et le nom de la commune ou est localisé son dossier.
FeatureJoiner_3
    ATTR_CONFLICT_RES = Use Left
    GEOMETRY_HANDLING = Use Left
    JOIN_KEYS = OBJECTID NUMERO_DOSSIER AUTO
    JOIN_MODE = Inner
    JOINED -> FeatureMerger_2 [REQUESTOR]
Note: Jointure de l'attribut repertoire pour créer le chemin du repertoire dans lequel le fichier est déplacer.
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> AttributeCreator_5
Note: Création du nouveau nom du fichier: OBJECTID+CODE_INSEE + EXTENSION
AttributeCreator_5
    ATTR_TABLE:
      SET_TO LIEN_FICHIER_RENOMMAGE_BASE = @Value(OBJECTID_MAX_PLUS_1)_$(NUMERO_DOSSIER)_@Value(CODE_INSEE).@Value(_extension)
      SET_TO nom_fichier = @Value(OBJECTID_MAX_PLUS_1)_$(NUMERO_DOSSIER)_@Value(CODE_INSEE).@Value(_extension)
      SET_TO source_fichier = $(FICHIER_A_DEPLACER)
      SET_TO chemin_fichier = @Value(REPERTOIRE)/$(NUMERO_DOSSIER)
    -> filecopy (writer FILECOPY_1)
    -> AttributeKeeper_2

Bookmark: Identification de la commune de localisation du dossier
TA_GG_DOSSIER (reader ORACLE_AUTONOMOUS_NONSPATIAL_1)
    attributes: OBJECTID number(38,0), FID_ETAT_AVANCEMENT number(38,0), FID_FAMILLE number, FID_PERIMETRE number(38,0), FID_PNOM_CREATION number(38,0), FID_PNOM_MODIFICATION number(38,0), DATE_SAISIE date, DATE_MODIFICATION date, DATE_CLOTURE date, DATE_DEBUT_LEVE date, DATE_FIN_LEVE date, DOS_DT_PREV date, DATE_DEBUT_TRAVAUX date, DATE_FIN_TRAVAUX date, DATE_COMMANDE_DOSSIER date, DOS_VOIE number(8,0), MAITRE_OUVRAGE varchar2(200), RESPONSABLE_LEVE varchar2(200), ENTREPRISE_TRAVAUX varchar2(200), DOS_PRECISION varchar2(100), REMARQUE varchar2(2048), DOS_OLD_ID varchar2(8), DOS_IDPERE number(38,0)
    -> FeatureReader [INITIATOR]
    -> FeatureJoiner_2 [RIGHT]
Note: Récupère la géométrie du dossier
FeatureReader
    ATTRIBUTES = G_GESTIONGEO.TA_GG_GEO,"OBJECTID,CODE_INSEE,SURFACE"
    ATTR_ACCUM_MODE = Only Use Result
    COMBINE_GEOM = Use Result
    DATASET = $(INSTANCE_PRODUCTION_ORACLE_12_C)
    FEATURETYPES = $(SCHEMAC_G_GESTIONGEO_TABLE_TA_GG_GEO)
    FORMAT = ORACLE_AUTONOMOUS_SPATIAL
    INTERACT = <No Spatial Filter>
    ORACLE_AUTONOMOUS_SPATIAL_CHUNK_SIZE = 200
    ORACLE_AUTONOMOUS_SPATIAL_CREATE_FEATURE_TABLES_FROM_DATA = Yes
    ORACLE_AUTONOMOUS_SPATIAL_HANDLE_MULTIPLE_SPATIAL_COLUMNS = NO
    ORACLE_AUTONOMOUS_SPATIAL_PARSE_MAPINFO_SYMBOLOGY = NO
    ORACLE_AUTONOMOUS_SPATIAL_PASSWORD = $(MDP_PRODUCTION_INSTANCE_ORACLE_12_C_SCHEMA_G_GESTIONGEO_LEC)
    ORACLE_AUTONOMOUS_SPATIAL_PERSISTENT_CONNECTION = YES
    ORACLE_AUTONOMOUS_SPATIAL_QUERY_FEATURE_TYPES_FOR_MERGE_FILTERS = Yes
    ORACLE_AUTONOMOUS_SPATIAL_READ_3D_POLYGON_AS_FACE = NO
    ORACLE_AUTONOMOUS_SPATIAL_REMOVE_SCHEMA_QUALIFIER = NO
    ORACLE_AUTONOMOUS_SPATIAL_SERVER_TYPE = ORACLE8i
    ORACLE_AUTONOMOUS_SPATIAL_SHOW_SYSTEM_TABLES = NO
    ORACLE_AUTONOMOUS_SPATIAL_USER_NAME = $(UTILISATEUR_G_GESTIONGEO_LEC)
    ORACLE_AUTONOMOUS_SPATIAL_USE_SEARCH_ENVELOPE = NO
    ORACLE_AUTONOMOUS_SPATIAL_USE_UNIFIED_DATE_ATTRS = YES
    OUTPUT_FEATURES_DISPLAY = Schema and Data Features
    SELECTED_PORTS = G_GESTIONGEO.TA_GG_GEO
    WHERE = OBJECTID = @Value(FID_PERIMETRE)
    G_GESTIONGEO.TA_GG_GEO -> FeatureJoiner_2 [LEFT]
Note: Joint la géométrie au numéro du dossier.
FeatureJoiner_2
    ATTR_CONFLICT_RES = Use Right
    GEOMETRY_HANDLING = Use Left
    JOIN_KEYS = OBJECTID FID_PERIMETRE AUTO
    JOIN_MODE = Inner
    JOINED -> AttributeKeeper_3
Note: On garde le seulement le nom de la commune de localisation. Il va servir à créer les nouveau nom des fichiers du dossier.
AttributeKeeper_3
    CREATE_BULK_MODE_FEATURES = NO
    KEEP_ATTRS = CODE_INSEE,OBJECTID
    -> Aggregator_2
Note: Aggregation des element suivant le code INSEE pour n'avoir qu'un seul élément.
Aggregator_2
    ACCUM_ATTRS_NAME = Use Attributes From One Feature
    AGGREGATE_TYPE = Homogeneous Collection (If Possible)
    MODE = Geometry - Assemble One Level
    SEP = ,
    AGGREGATE -> FeatureJoiner_3 [LEFT]

Bookmark: MISE A jour de la table TA_GG_FICHIER + copie du fichier dans son répertoire dossier
AttributeKeeper_2
    CREATE_BULK_MODE_FEATURES = NO
    KEEP_ATTRS = INTEGRATION,LIEN_FICHIER_RENOMMAGE_BASE,OBJECTID_MAX_PLUS_1,NUMERO_DOSSIER
    -> TA_GG_URL_FILE (writer ORACLE_AUTONOMOUS_NONSPATIAL_3)
Note: MISE à jour de la colonne DOS_URL_FILE dans la table TA_GG_FICHIER
TA_GG_URL_FILE (writer ORACLE_AUTONOMOUS_NONSPATIAL_3)
    attributes: FICHIER varchar2(250), INTEGRATION number, OBJECTID number, FID_DOSSIER number
Note: Copie du fichier dans son repertoire fichier
filecopy (writer FILECOPY_1)
    attributes: filecopy_source_dataset char(512), filecopy_dest_dataset char(512), filecopy_dest_filename char(128)
